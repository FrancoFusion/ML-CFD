import FreeCAD
import Part
from FreeCAD import Vector, Rotation, Placement
import random
import math
import FreeCADGui

# Create a new FreeCAD document
DOC = FreeCAD.ActiveDocument
if DOC is None:
    DOC = FreeCAD.newDocument("PlateWithPath")

# Plate vertices on the ZY plane
plate_vertices = [
    (0, 0, 0),
    (0, 180, 0),
    (0, 180, 43.5),
    (0, 197, 43.5),
    (0, 197, 56.5),
    (0, 180, 56.5),
    (0, 180, 100),
    (0, 0, 100),
    (0, 0, 56.5),
    (0, -17, 56.5),
    (0, -17, 43.5),
    (0, 0, 43.5)
]

# Create edges between consecutive vertices
edges = []
num_vertices = len(plate_vertices)
for i in range(num_vertices):
    start = plate_vertices[i]
    end = plate_vertices[(i + 1) % num_vertices]
    edge = Part.makeLine(Vector(*start), Vector(*end))
    edges.append(edge)

# Create a wire and face from the edges
wire = Part.Wire(edges)
face = Part.Face(wire)

# Extrude the face to create the plate solid in the positive X direction
plate_thickness = 3  # Thickness of the plate
plate_solid = face.extrude(Vector(plate_thickness, 0, 0))

# Add the plate solid to the document
plate_obj = DOC.addObject("Part::Feature", "Plate")
plate_obj.Shape = plate_solid

# Define the path points on the top surface of the plate (X=3 mm)
x_top_surface = plate_thickness  # X coordinate of the top surface
start_point = (x_top_surface, -17, 50)
first_permanent_point = (x_top_surface, 10, 50)
second_permanent_point = (x_top_surface, 180, 50)
end_point = (x_top_surface, 197, 50)

# Generate random points within boundaries, 15 mm margin to the sides
num_random_points = 3
y_min, y_max = 30, 150  # Y bounds with margin from the sides of the plate
z_min, z_max = 10, 90   # 20, 85 Z bounds with margin from top and bottom
min_spacing = 30  # Minimum distance between consecutive points

random_points = []
while len(random_points) < num_random_points:
    # Generate a candidate point within the margin boundaries
    y = random.uniform(y_min, y_max)
    z = random.uniform(z_min, z_max)
    new_point = (x_top_surface, y, z)

    # Check distance to the last accepted point
    if random_points:
        last_point = random_points[-1]
        distance = math.sqrt((new_point[1] - last_point[1])**2 + (new_point[2] - last_point[2])**2)
        
        # Ensure spacing meets the minimum distance requirement
        if distance < min_spacing:
            continue  # Skip this point if too close, generate a new one

    # Accept the point if it meets the spacing requirement
    random_points.append(new_point)

# Sort random points by Y value to maintain order along the Y-axis
random_points.sort(key=lambda point: point[1])

# Create the path segments with smooth connections
# Segment 1: Straight line from start_point to first_permanent_point
edge1 = Part.makeLine(Vector(*start_point), Vector(*first_permanent_point))

# Segment 2: Spline curve through random points including permanent points for smoothness
spline_points = [first_permanent_point] + random_points + [second_permanent_point]
spline_curve = Part.BSplineCurve()
spline_curve.interpolate([Vector(*pt) for pt in spline_points])
spline_edge = spline_curve.toShape()

# Segment 3: Straight line from second_permanent_point to end_point
edge3 = Part.makeLine(Vector(*second_permanent_point), Vector(*end_point))

# Combine all segments into a single wire
path_edges = [edge1, spline_edge, edge3]
path_wire = Part.Wire(path_edges)

# Add the path to the document (optional, for visualization)
path_obj = DOC.addObject("Part::Feature", "Path")
path_obj.Shape = path_wire

# Create the rectangle profile on the XZ plane at the starting point
profile_width = 10  # Total width (5 mm on each side of the path)
profile_height = 1.5  # Height (depth into the plate)

# Define the rectangle in the XZ plane, centered at the path
p1 = Vector(profile_height, 0, -profile_width / 2)
p2 = Vector(0, 0, -profile_width / 2)
p3 = Vector(0, 0, profile_width / 2)
p4 = Vector(profile_height, 0, profile_width / 2)

# Create edges of the rectangle
rect_edges = [
    Part.makeLine(p1, p2),
    Part.makeLine(p2, p3),
    Part.makeLine(p3, p4),
    Part.makeLine(p4, p1)
]

# Make a wire from edges
rectangle_wire = Part.Wire(rect_edges)

# Position and rotate the rectangle at the starting point of the path
# Rotate 90 degrees additionally along the Y-axis for correct orientation
rect_placement = Placement(Vector(*start_point), Rotation(Vector(0, 1, 0), -180))
rectangle_wire.Placement = rect_placement

# Add the profile to the document for sweeping
profile_obj = DOC.addObject("Part::Feature", "Profile")
profile_obj.Shape = rectangle_wire

# Perform the sweep using the path and the profile
sweep_obj = DOC.addObject("Part::Sweep", "Fluid")
sweep_obj.Sections = [profile_obj]
sweep_obj.Spine = path_obj
sweep_obj.Solid = True  # Ensures the solid has closed ends
sweep_obj.Frenet = False  # Keeps the profile orthogonal to the path

# Recompute the document to update the view
DOC.recompute()

# Create a copy of the fluid object to retain it in the document
fluid_copy = DOC.addObject("Part::Feature", "Fluid")
fluid_copy.Shape = sweep_obj.Shape
fluid_copy.ViewObject.DisplayMode = "Shaded"
#fluid_copy.ViewObject.LineWidth = 1  # Optional: Set line width to 0 to hide edges completely


# Perform a Boolean cut to remove the intersecting part from the plate
cut_obj = DOC.addObject("Part::Cut", "PlateWithFluidCut")
cut_obj.Base = plate_obj
cut_obj.Tool = sweep_obj
DOC.recompute()

# Make sure both the carved plate and the fluid part are visible as separate objects
fluid_copy.ViewObject.Visibility = True
cut_obj.ViewObject.Visibility = True

# Get the active 3D view
view = FreeCADGui.ActiveDocument.ActiveView

# Set the view direction
view.setViewDirection(FreeCAD.Vector(-1, 0, 0))

# fit all objects in the view
view.fitAll()

view.viewAxometric()

DOC.recompute()
